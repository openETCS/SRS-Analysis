# Specification: Specification Document
- Description: Requirements Document

## Geographical position reporting
Part 3.6.6 of Subset-026-3
- Subset26Reference: 3.6.6

### R3
The ERTMS/ETCS on-board equipment shall display, only on driver request,  the geographical position of the estimated front end of the train in relation to the track kilometre. The display of the geographical position shall also be stopped on driver request.
- Subset26Reference: 3.6.6.1

#### R2
The Kernel shall provide the geographical position of the estimated front end of the train in relation to the track kilometre to the DMI.
- Splitting reason: Reduce kernel function

#### R4
The DMI shall display, on driver request, the geographical position of the estimated front end of the train in relation to the track kilometre. The display of the geographical position shall also be stopped on driver request.
